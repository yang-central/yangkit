module test-string-xsd-regex {
    yang-version 1.1;
    namespace "urn:xml:test:string:xsd";
    prefix xsr;

    revision 2026-04-01 {
        description "XML Schema regex codec regression test.";
    }

    container string-container {
        config false;

        leaf identifier {
            type string {
                pattern "\\i\\c*";
            }
        }

        leaf basic-latin {
            type string {
                pattern "\\p{IsBasicLatin}+";
            }
        }

        leaf anchor-literal {
            type string {
                pattern "^a$";
            }
        }

        leaf non-identifier {
            type string {
                pattern "\\i\\c*" {
                    modifier invert-match;
                }
            }
        }
    }
}
