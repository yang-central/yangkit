module outer-anydata {
  yang-version 1.1;
  namespace "urn:test:outer-anydata";
  prefix outer;

  container anydata-wrapper {
    anydata payload-holder;

    list entry {
      key "name";
      leaf name {
        type string;
      }
      anydata payload-holder;
    }
  }
}
