module insa-test{
    yang-version 1.1;
    namespace "urn:ietf:params:xml:ns:yang:insa-test";
    prefix ity;

    organization "INSA LYON";
    contact
        "Authors:  Vivekananda Boudia
        <mailto:vivekananda.boudia@insa-lyon.fr>
        Copyright 2023 INSA Lyon.

        Licensed under the Apache License, Version 2.0 (the 'License');
        you may not use this file except in compliance with the License.
        You may obtain a copy of the License at

        http://www.apache.org/licenses/LICENSE-2.0

        Unless required by applicable law or agreed to in writing, software
        distributed under the License is distributed on an 'AS IS' BASIS,
        WITHOUT WARRANTIES OR CONDITIONS OF ANY KIND, either express or implied.
        See the License for the specific language governing permissions and
        limitations under the License.";

    description
        "Yang module used for unit test for derived type";

    revision 2023-12-16 {
        description "Initial version.";
    }

    typedef base1 {
        type string {
            length "1..3";
        }
    }

    typedef base2 {
        type string {
            pattern "a+";
        }
    }

    typedef base3 {
        type string {
            length "1..3";
        }
    }

    container insa-container {
        config false;
        leaf derived1{
            type base1 {
                length "1..2";
            }
        }
        leaf derived2{
            type base2 {
                length "1..2";
            }
        }
        leaf derived3{
            type base3 {
                pattern "b+";
            }
        }
    }
}
