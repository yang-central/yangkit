module insa-test {
    yang-version 1.1;
    namespace "urn:ietf:params:xml:ns:yang:insa-test";
    prefix ity;

    organization "INSA Lyon";
    contact
        "Authors:  Alex huang Feng
        <mailto:alex.huang-feng@insa-lyon.fr>
        Copyright 2023 INSA Lyon.

        Licensed under the Apache License, Version 2.0 (the 'License');
        you may not use this file except in compliance with the License.
        You may obtain a copy of the License at

        http://www.apache.org/licenses/LICENSE-2.0

        Unless required by applicable law or agreed to in writing, software
        distributed under the License is distributed on an 'AS IS' BASIS,
        WITHOUT WARRANTIES OR CONDITIONS OF ANY KIND, either express or implied.
        See the License for the specific language governing permissions and
        limitations under the License.";

    description
        "insa-test YANG module.";

    revision 2023-09-05 {
        description "Initial version.";
    }

    container insa-container {
        config false;
        leaf computer {
            type string;
            mandatory true;
            description "computer";
        }
        leaf router {
            type uint8;
            description "router";
        }
    }
}
