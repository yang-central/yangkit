module insa-test{
    yang-version 1.1;
    namespace "urn:ietf:params:xml:ns:yang:insa-test";
    prefix ity;

    organization "INSA LYON";
    contact
        "Authors:  Vivekananda Boudia
        <mailto:vivekananda.boudia@insa-lyon.fr>
        Copyright 2023 INSA Lyon.

        Licensed under the Apache License, Version 2.0 (the 'License');
        you may not use this file except in compliance with the License.
        You may obtain a copy of the License at

        http://www.apache.org/licenses/LICENSE-2.0

        Unless required by applicable law or agreed to in writing, software
        distributed under the License is distributed on an 'AS IS' BASIS,
        WITHOUT WARRANTIES OR CONDITIONS OF ANY KIND, either express or implied.
        See the License for the specific language governing permissions and
        limitations under the License.";

    description
        "Yang module used for unit test";

    revision 2023-12-30 {
        description "Initial version.";
    }
    container network {
        description "Represents a network configuration.";

        list nodes {
            key "id";
            description "List of nodes in the network.";

            leaf id {
                type string;
                description "Unique identifier for the node.";
            }

            leaf name {
                type string;
                description "Human-readable name of the node.";
            }

            container interfaces {
                description "Network interfaces of the node.";

                list interface {
                    key "name";
                    description "List of interfaces on the node.";

                    leaf name {
                        type string;
                        description "Name of the interface.";
                    }

                    leaf enabled {
                        type boolean;
                        description "Indicates if the interface is enabled.";
                    }

                    leaf interface-type {
                        type enumeration {
                            enum ethernet;
                            enum wifi;
                            enum virtual;
                        }
                        description "Type of the interface.";
                    }

                    leaf ip-address {
                        type string;
                        description "IPv4 address of the interface.";
                    }
                }
            }
        }
    }
}
