module schema-path-augment {
  yang-version 1.1;
  namespace "urn:test:schema-path-augment";
  prefix spa;

  import ietf-yang-structure-ext { prefix sx; }
  import test-structure { prefix ts; }

  sx:augment-structure "/ts:message/ts:payload" {
    leaf extra { type string; }
  }
}
