module payload-anydata {
  yang-version 1.1;
  namespace "urn:test:payload-anydata";
  prefix payload;

  container payload-root {
    leaf value {
      type string;
      mandatory true;
      must ". = 'abc'";
    }

    list item {
      key "id";
      min-elements 1;
      max-elements 2;

      leaf id {
        type string;
      }

      leaf name {
        type string;
        mandatory true;
      }
    }

    leaf target {
      type string;
    }

    leaf selected-target {
      type leafref {
        path "../target";
      }
    }
  }
}
