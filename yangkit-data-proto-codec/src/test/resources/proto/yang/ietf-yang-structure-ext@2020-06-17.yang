module ietf-yang-structure-ext {
  yang-version 1.1;
  namespace "urn:ietf:params:xml:ns:yang:ietf-yang-structure-ext";
  prefix sx;

  revision 2020-06-17 {
    description
      "Minimal test copy of RFC 8791 structure extension for protobuf codec tests.";
    reference
      "RFC 8791: YANG Data Structure Extensions.";
  }

  extension structure {
    argument name {
      yin-element true;
    }
    description
      "Minimal structure extension used by tests.";
  }
}
