module test-proto-structure {
    yang-version 1.1;
    namespace "urn:example:test-proto-structure";
    prefix tps;
    import ietf-yang-structure-ext {
        prefix sx;
    }
    revision 2026-04-02 {
        description "Initial structure test module for protobuf codec regression tests.";
    }
    sx:structure message {
        description "Top-level structure used to verify RFC 8791 parser/model discovery in protobuf tests.";
        container metadata {
            leaf timestamp {
                type string;
                mandatory true;
            }
            leaf source {
                type string;
            }
            leaf sequence-number {
                type uint32;
            }
        }
        container payload {
            leaf data-type {
                type string;
            }
            leaf content {
                type string;
            }
        }
    }
}
