module null-pointer-example {
  yang-version 1.1;
  namespace "urn:example:yangkit-bug";
  prefix bug;

  description
    "Demonstrate NullPointerException in io.github.yang-central.yangkit:yangkit-parser:1.3.5";

  revision 2023-07-25 {
  }

  typedef package-version {
    type string {
      pattern '\d+\.\d+([-.](\d+|\w+))*';
    }
  }

  grouping package-meta-data {
    typedef version {
      type package-version;
    }
  }
}
